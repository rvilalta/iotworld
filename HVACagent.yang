module HVACagent {
    namespace "urn:CTTC:HVACagent";
    prefix HVACagent;
    organization "CTTC";
    contact "ricard(dot)vilalta(at)cttc(dot)es";
    description "YANG model for a HVAC agent";
    revision 2016-06-17 {
        description "Latest revision";
    }
    
	typedef Status {
		type enumeration {
			 enum Stop;
			 enum Run;
			 enum Error;
		}
	}
	 
    grouping Temperature {
        leaf TempCentigrads {
            type decimal64 {
                fraction-digits 1;
            }
        }
    }
    
    grouping Heat {
        leaf Status {
			type Status;
		}
    }
    
	grouping Ac {
		leaf Status {
			type Status;
		}
	}
	
	grouping HVAC {
	    container Temperature { 
    		uses Temperature;
        }
		container Heat {
		    uses Heat;
		}
		container Ac {
		    uses Ac;	
		}
	}
	
	container HVAC {
		uses HVAC;
	}
	
}
